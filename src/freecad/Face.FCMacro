import Part


class ViewObserver:

   def RemoveCallback(self):
        self.v.removeEventCallback("SoMouseButtonEvent",self.c)

   def logPosition(self, info):
       if info["Button"] == "BUTTON2" and info["State"] == "DOWN":
          print( "Removing callback." )
          print(self)
          self.RemoveCallback()
       else:
           if FreeCADGui.Selection.getSelectionEx():
               detail()
               self.RemoveCallback()

   def RecordCallback(self, view, callback):
        print("Recording callback")
        self.v = view
        self.c = callback

def detail():
        sel = FreeCADGui.Selection.getSelectionEx()[0]   # Select an object
        if sel != 0:                           # If there is a selection then
            for i in enumerate(sel.SubObjects):
                if type(i[1]) == Part.Face:
                    print(i[1].normalAt(0,0))
                    for j in i[1].Edges:
                        print( j.Curve )

def CheckSelected():
    if not FreeCADGui.Selection.getSelectionEx():
        o = ViewObserver()
        v=Gui.activeDocument().activeView()
        c = v.addEventCallback("SoMouseButtonEvent",o.logPosition)
        o.RecordCallback(v,c)
    else:
        detail()

CheckSelected()
